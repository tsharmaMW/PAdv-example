# HighLevelReqs

## HLR: High-Level Software Requirements for Helicopter Fight Control System (Container)

### INTRO: Introduction (Informational)
This document provides the high-level software requirements for a helicopter flight control system that provides attitude and attitude rate control based on pilot input commands.

### DESCR: System Description (Informational)
The flight control system is made up of pilot commands, cyclic and pedals, a flight control computer, hydraulic actuators of the main and tail rotors, and attitude and rate sensors. A diagram of the overall system is shown in the figure below.
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The cyclic controls the pitch of the main rotor blades allowing the helicopter to pitch up or down and roll right or left. The pedals control the pitch of the tail rotor allowing the helicopter to yaw right or left. This control system does not include the throttle and collective that work in coordination to control the total lift of the helicopter.
This document defines the high-level software requirements for the Flight Control Computer.

### REQS: High-Level Software Requirements (Container)
This section provides the high-level requirements for the flight control computer software. Each requirement is labeled with a unique numeric identifier that is appended to an HLR_ prefix. These labels serve as anchors to which the software design and software verification cases can trace.

#### HLR_1: Pilot Input Signal Processing (Functional)
The flight control computer software shall process three linear variable differential transformer (LVDT) inputs from the pilot cockpit controls, including cyclic fore/aft position, cyclic left/right position, and left/right pedal position. The software receives each of the LVDT positions as a 16-bit signed integer input from the hardware.
The characteristics of the LVDT inputs to the software and their relations to the pilot commands are given in the following table:
| Signal | LVDT Input Sign | LVDT Input Range | Software Input Range | Pilot Command Scaling |
| --- | --- | --- | --- | --- |
| Fore/aft cyclic | Aft = + | +/- 2 inches | -32768 to +32767 | 15 degrees/inch |
| Left/right cyclic | Right = + | +/- 2 inches | -32768 to +32767 | 15 degrees/inch |
| Left/right pedal | Right = + | +/- 3 inches | -32768 to +32767 | 5 degrees/second/inch |

#### HLR_2: Hydraulic Actuator Feedback (Functional)
The flight control computer software shall process three linear variable differential transformer (LVDT) inputs from the hydraulic actuators, including fore/aft main rotor control, left/right main rotor control, and left/right tail rotor control. The software receives each of the LVDT positions as a 16-bit signed integer input from the hardware.
The characteristics of the LVDT inputs to the software are given in the following table:
| Signal | LVDT Input Sign | LVDT Input Range | Software Input Range |
| --- | --- | --- | --- |
| Fore/aft main rotor feedback | Aft = + | +/- 0.1 meter | -32768 to +32767 |
| Left/right main rotor feedback | Right = + | +/- 0.1 meter | -32768 to +32767 |
| Left/right tail rotor feedback | Right = + | +/- 0.1 meter | -32768 to +32767 |

#### HLR_3: Hydraulic Actuator Drive (Functional)
The flight control computer software shall drive three electrohydraulic valve (EHV) outputs, one to each of the hydraulic actuators. The software provides each of the EHV commands as a 16-bit signed integer output to the hardware.
The characteristics of the EHV outputs from the software are defined in the following table:
| Signal | EHV Input Sign | EHV Input Range | Software Output Range |
| --- | --- | --- | --- |
| Fore/aft main rotor command | Aft = + | +/- 0.3 inch | -32768 to +32767 |
| Left/right main rotor command | Right = + | +/- 0.3 inch | -32768 to +32767 |
| Left/right tail rotor command | Right = + | +/- 0.3 inch | -32768 to +32767 |

#### HLR_4: Hydraulic Actuator Loop Control (Functional)
The flight control computer software shall provide a control loop for each of the hydraulic actuators. Each hydraulic actuator loop receives a position reference from an attitude/rate control, and a position feedback from one of the processed LVDT sensor inputs.
Each hydraulic actuator loop shall implement a proportional-integral-derivative (PID) controller with the following characteristics:
· The proportional gain shall be 0.135.
· The integral gain shall be 0.00122. The integral shall implement a Forward Euler integrator with an anti-windup method.
· The derivative gain shall be -0.00134. The derivative shall implement a Forward Euler filter with a coefficient of 1/0.0157.
· The output limit shall be +/- 0.3 inch.
Each hydraulic actuator loop shall operate at a rate of 1 millisecond.

#### HLR_5: Multi-Variable Inner Loop Control (Functional)
The flight control computer software shall provide an inner control loop for pitch, roll, and yaw rate with low-pass filters that cutoff at 40 radians/second. The inner loop receives pitch, roll, and yaw rate corrections from an outer loop, and pitch, roll, yaw rate, pitch rate, and roll rate feedbacks from the processed AHRS data.
The following (5x3) gain shall be used to convert the (5x1) AHRS data to the (3x1) static output feedback:
| 2.211000 | -0.310000 | -0.003360 | 0.785400 | -0.015180 |
| --- | --- | --- | --- | --- |
| -0.192300 | -1.291000 | 0.018200 | -0.085020 | -0.119500 |
| -0.019360 | -0.012050 | -1.895000 | -0.004121 | 0.067970 |
The output limit shall be +/- 0.1 meter due to mechanical limits of the hydraulic actuators. The inner loop control shall operate at a rate of 10 milliseconds.

#### HLR_6: Pitch Outer Loop Control (Functional)
The flight control computer software shall provide an outer control loop for pitch. The pitch outer loop receives a pitch command from one of the processed LVDT pilot inputs, and a pitch feedback from the processed AHRS data.
The pitch outer loop shall implement a proportional-integral (PI) controller with the following characteristics:
· The proportional gain shall be 1.04.
· The integral gain shall be 2.07. The integral shall implement a Forward Euler integrator with an integral limit of +/- 30 degrees.
· The output limit shall be +/- 30 degrees.
The pitch outer loop control shall operate at a rate of 10 milliseconds.

#### HLR_7: Roll Outer Loop Control (Functional)
The flight control computer software shall provide an outer control loop for roll. The roll outer loop receives a roll command from one of the processed LVDT pilot inputs, and a roll feedback from the processed AHRS data.
The roll outer loop shall implement a proportional-integral (PI) controller with the following characteristics:
· The proportional gain shall be -0.0991.
· The integral gain shall be -1.35. The integral shall implement a Forward Euler integrator with an integral limit of +/- 30 degrees.
· The output limit shall be +/- 30 degrees.
The roll outer loop control shall operate at a rate of 10 milliseconds.

#### HLR_8: Yaw Rate Outer Loop Control (Functional)
The flight control computer software shall provide an outer control loop for yaw rate. The yaw rate outer loop receives a yaw rate command from one of the processed LVDT pilot inputs, and a yaw rate feedback from the processed AHRS data.
The yaw rate outer loop shall implement a proportional-integral (PI) controller with the following characteristics:
· The proportional gain shall be 0.137.
· The integral gain shall be -2.2. The integral shall implement a Forward Euler integrator with an integral limit of +/- 15 degrees/second.
· The output limit shall be +/- 15 degrees/second.
The yaw rate outer loop control shall operate at a rate of 10 milliseconds.

#### HLR_9: AHRS Validity Check (Functional)
The flight control computer software shall verify if the data from an AHRS is valid prior to using it.

#### HLR_10: AHRS Input Signal Processing (Functional)
The flight control computer software shall process three AHRS digital bus inputs.
The characteristics of the AHRS inputs, from each of the three sensors, to the software are given in the following table:
| Signal | Input Sign | Input Range |
| --- | --- | --- |
| AHRS Valid | N/A | 1 = Valid, 0 = Invalid |
| Pitch Attitude | Up = + | +/- 90 degrees |
| Roll Attitude | Right = + | +/- 180 degrees |
| Yaw body rate | Right = + | +/- 60 degrees/second |
| Pitch body rate | Up = + | +/- 60 degrees/second |
| Roll body rate | Right = + | +/- 60 degrees/second |

#### HLR_11: AHRS Voting for Triple Sensors (Functional)
When all three AHRSs are valid, the flight control computer software shall use the middle value of each parameter from all three sensors.

#### HLR_12: AHRS Voting for Dual Sensors (Functional)
When only two AHRSs are valid, the flight control computer software shall use the average value of each parameter from the two valid sensors.

#### HLR_13: AHRS Usage of Single Sensor (Functional)
When only one AHRS is valid, the flight control computer software shall use the value of each parameter from the sole valid sensor.

#### HLR_14: AHRS Usage of No Sensor (Functional)
When no AHRS is valid, the flight control computer software shall ignore the value of each parameter from all three sensors and set the value of each parameter to zero.

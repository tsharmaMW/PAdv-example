# SystemReqs

## SR: System Requirements for Helicopter Fight Control System (Container)

### INTRO: Introduction (Informational)
This document provides the system level requirements for a helicopter flight control system that provides attitude and attitude rate control based on pilot input commands.

### DESCR: System Description (Informational)
The flight control system is made up of pilot commands, cyclic and pedals, a flight control computer, hydraulic actuators of the main and tail rotors, and attitude and rate sensors. A diagram of the overall system is shown in the figure below.
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The cyclic controls the pitch of the main rotor blades allowing the helicopter to pitch up or down and roll right or left. The pedals control the pitch of the tail rotor allowing the helicopter to yaw right or left. This control system does not include the throttle and collective that work in coordination to control the total lift of the helicopter.

### REQS: System Requirements (Container)
This section provides the system level requirements for the flight control system. Each requirement is labeled with a unique numeric identifier that is appended to an SR_ prefix. These labels serve as anchors to which the high-level software requirements and system verification cases can trace.

#### SR_1: Pilot Input Signals (Functional)
The flight control system shall process three linear variable differential transformer (LVDT) inputs from the pilot cockpit controls, including cyclic fore/aft position, cyclic left/right position, and left/right pedal position.

#### SR_2: Hydraulic Actuator Interfaces (Functional)
The flight control system shall interface with three hydraulic actuators, two for controlling the main rotor and one for controlling the tail rotor.

#### SR_3: Hydraulic Actuator Signals (Functional)
Each hydraulic actuator interface shall have an electrohydraulic valve (EHV) that controls the actuator and a linear variable differential transformer (LVDT) sensor that feedbacks the piston position.

#### SR_4: Hydraulic Actuator Control Loop Performance (Functional)
The flight control system shall control the hydraulic actuator position with a minimum bandwidth of 10Hz and a minimum damping of 0.4. The flight control system shall track position command to a steady-state error of 5% or less.

#### SR_5: Attitude Heading Reference System Interfaces (Functional)
The flight control system shall process three MIL1553 digital bus inputs from Attitude/Heading Reference Systems (AHRS), including pitch, roll, yaw rate, pitch rate, and roll rate.

#### SR_6: Attitude Rate Tracking Performance (Functional)
The flight control system shall track pitch and roll set point changes to a steady-state error of 1 degree or less, a rise time of about 2 seconds, and a maximum overshoot of 10%. The flight control system shall track yaw rate set point changes to a steady-state error of 0.5 degree/second or less, a rise time of about 2 seconds, and a maximum overshoot of 10%.

#### SR_7: Control Bandwidth (Functional)
The control bandwidth shall be limited to 40 radians/second in order to guard against high-frequency rotor dynamics and measurement noise.

#### SR_8: Control Gain and Phase Margins (Functional)
The gain margin shall be at a minimum of 10dB and the phase margin shall be at a minimum of 45 degrees in all axes.

#### SR_9: Attitude Rate Authority Limiting (Functional)
The flight control system shall limit the pitch and roll to 30 degrees, +/-10%. The yaw rate shall be limited to 15 degrees/second, +/- 10%.

#### SR_10: Sensor Validation (Functional)
The flight control system shall determine the validity of each of the three AHRS prior to using the data from them.

#### SR_11: Sensor Voting (Functional)
When all of the AHRSs are valid, the flight control system shall use the middle value of each parameter from all three AHRSs. When only two of the AHRSs are valid, the flight control system shall use the average value of each parameter from the two valid AHRSs. When only one of the AHRSs is valid, the flight control system shall use the value of each parameter from the sole valid AHRS. When none of the AHRSs is valid, the flight control system shall ignore the value of each parameter from all three AHRSs.
